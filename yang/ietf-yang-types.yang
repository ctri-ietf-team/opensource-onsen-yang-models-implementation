module ietf-yang-types {
  yang-version 1.1;
  namespace "urn:ietf:params:xml:ns:yang:ietf-yang-types";
  prefix yang;

  organization
    "IETF NETMOD (NETCONF Data Modeling Language) Working Group";
  contact
    "WG Web:   <https://datatracker.ietf.org/wg/netmod/>";
  description
    "This module contains a collection of generally useful derived
     YANG data types. CORE SUBSET for L3VPN mapping prototype.";

  revision 2013-07-15 {
    description
      "This revision adds the following new data types:
       - yang:date-and-time
       - yang:gauge64
       - yang:dotted-quad";
    reference
      "RFC 6991: Common YANG Data Types";
  }

  typedef counter32 {
    type uint32;
    description
      "The counter32 type represents a non-negative integer
       that monotonically increases until it reaches a
       maximum value of 2^32-1 (4294967295 decimal).";
    reference
      "RFC 2863: The Interfaces Group MIB";
  }

  typedef counter64 {
    type uint64;
    description
      "The counter64 type represents a non-negative integer
       that monotonically increases until it reaches a
       maximum value of 2^64-1 (18446744073709551615
       decimal).";
    reference
      "RFC 2863: The Interfaces Group MIB";
  }

  typedef gauge32 {
    type uint32;
    description
      "The gauge32 type represents a non-negative integer,
       which may increase or decrease, but shall never exceed
       a maximum value.";
    reference
      "RFC 2863: The Interfaces Group MIB";
  }

  typedef gauge64 {
    type uint64;
    description
      "The gauge64 type represents a non-negative integer,
       which may increase or decrease, but shall never exceed
       a maximum value.";
    reference
      "RFC 6991: Common YANG Data Types";
  }

  typedef object-identifier {
    type string {
      pattern '(([0-1](\.[1-3]?[0-9]))|(2\.(0|([1-9]\d*))))'
            + '(\.(0|([1-9]\d*)))*';
    }
    description
      "The object-identifier type represents administratively
       assigned names in a registration-hierarchical-name tree.";
    reference
      "ITU-T X.660: Information technology - Open Systems
       Interconnection - Procedures for the operation of OSI
       Registration Authorities: General procedures and top
       arcs of the ASN.1 Object Identifier tree";
  }

  typedef object-identifier-128 {
    type object-identifier {
      pattern '\d*(\.\d*){1,127}';
    }
    description
      "This type represents object-identifiers restricted to 128
       sub-identifiers.";
    reference
      "RFC 6991: Common YANG Data Types";
  }

  typedef date-and-time {
    type string {
      pattern '\d{4}-\d{2}-\d{2}T\d{2}:\d{2}:\d{2}(\.\d+)?'
            + '(Z|[\+\-]\d{2}:\d{2})';
    }
    description
      "The date-and-time type is a profile of the ISO 8601
       standard for representation of dates and times using the
       Gregorian calendar.";
    reference
      "RFC 3339: Date and Time on the Internet: Timestamps";
  }

  typedef timeticks {
    type uint32;
    description
      "The timeticks type represents a non-negative integer that
       represents the time, modulo 2^32 (4294967296 decimal), in
       hundredths of a second between two epochs.";
    reference
      "RFC 2863: The Interfaces Group MIB";
  }

  typedef timestamp {
    type yang:timeticks;
    description
      "The timestamp type represents the value of an associated
       timeticks object at which a specific occurrence happened.";
    reference
      "RFC 2863: The Interfaces Group MIB";
  }

  typedef phys-address {
    type string {
      pattern '([0-9a-fA-F]{2}(:[0-9a-fA-F]{2})*)?';
    }
    description
      "Represents media- or physical-level addresses represented
       as a sequence octets, each octet represented by two
       hexadecimal numbers.";
    reference
      "RFC 2863: The Interfaces Group MIB";
  }

  typedef mac-address {
    type string {
      pattern '[0-9a-fA-F]{2}(:[0-9a-fA-F]{2}){5}';
    }
    description
      "The mac-address type represents an IEEE 802 MAC address.";
    reference
      "IEEE 802: IEEE Standard for Local and Metropolitan Area
       Networks: Overview and Architecture";
  }

  typedef xpath1.0 {
    type string;
    description
      "This type represents an XPATH 1.0 expression.";
    reference
      "XPATH 1.0: XML Path Language (XPath) Version 1.0";
  }

  typedef hex-string {
    type string {
      pattern '([0-9a-fA-F]{2}(:[0-9a-fA-F]{2})*)?';
    }
    description
      "A hexadecimal string with octets represented as hex digits
       separated by colons.";
    reference
      "RFC 6991: Common YANG Data Types";
  }

  typedef uuid {
    type string {
      pattern '[0-9a-fA-F]{8}-[0-9a-fA-F]{4}-[0-9a-fA-F]{4}-'
            + '[0-9a-fA-F]{4}-[0-9a-fA-F]{12}';
    }
    description
      "A Universally Unique IDentifier in the string representation
       defined in RFC 4122.";
    reference
      "RFC 4122: A Universally Unique IDentifier (UUID) URN
       Namespace";
  }

  typedef dotted-quad {
    type string {
      pattern '(([0-9]|[1-9][0-9]|1[0-9][0-9]|2[0-4][0-9]|25[0-5])\.){3}'
            + '([0-9]|[1-9][0-9]|1[0-9][0-9]|2[0-4][0-9]|25[0-5])';
    }
    description
      "An unsigned 32-bit number expressed in the dotted-quad
       notation.";
    reference
      "RFC 6991: Common YANG Data Types";
  }
}
